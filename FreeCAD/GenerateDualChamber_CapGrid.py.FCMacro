#=============== NIF GenerateDualChamber.py ================
# 

import FreeCAD as App
import Part
import Draft
import numpy as np
from PySide import QtGui
from BOPTools import BOPFeatures


#======== Apply fillet to object edges
def FilletEdges(Object, FilletName, FilletEdges, FilletRadius):
	Fillet 		= doc.addObject("Part::Fillet", FilletName)
	Fillet.Base 	= Object
	__fillets__ = []
	for n in FilletEdges:
	  __fillets__.append((n, FilletRadius, FilletRadius))
	Fillet.Edges 		= __fillets__
	Object.Visibility 	= False
	del __fillets__
	return Fillet
	#FreeCADGui.ActiveDocument.ConnectorBlock.Visibility = False

#======== Apply chamfer to object edges
def ChamferEdges(Object, ChamferName, ChamferEdges, ChamferRadius):
	Chamfer 	= doc.addObject("Part::Chamfer", ChamferName)
	Chamfer.Base	= Object
	__fillets__ = []
	for n in ChamferEdges:
	  __fillets__.append((n,ChamferRadius, ChamferRadius))
	Chamfer.Edges 	= __fillets__
	Object.Visibility 	= False
	del __fillets__
	return Chamfer


## =============== Set chamber parameters
filename 					= 'NIF_DualChamber'
Elec_Distance 				= 9		# Distance between the 2 electrodes
Elec_RadiusA  				= 5		# Radius of ichamber aroudn electrode A
Elec_RadiusB 				= 5		# Radius of chamber around electrode B
WallThickness 				= 4 		# Minimum thickness of chamber walls at base

# Chamber cap lip and screw holes
GridDepth 					= 5 		# Vertical depth of grid
GridLipThickness 			= 1 		# Width / thickness of grid lip (top rim of chamber)
CapLipDepth 				= 8		# Vertical depth of cap overlap with top of chamber
CapScrewDiam				= 3		# Diameter of cap screws
CapScrewHoleDepth 			= 2		# Depth of cap screw holes into chamber surface
CapScrewHeight 			= CapScrewDiam
CapScrewChamferRadius 		= 1		# Radius of chamfer used on cap screw holes on chamber surface
CapScrewCutDepth 			= CapScrewHoleDepth*4

# Connector block size and orientation
CB_Width 					= 20			# Width of connector block base (4 x Omnetics 36-pin ~= 20mm)
CB_Length					= 25	 		# Length of connector block base
CB_Height 					= 6			# Height of connector block base
CB_Rotation_XYZ 			= [90, 0, 0]		# Angle of connector block rotation relative to line orthogonal to line bisecting electrode centers
CB_filletRadius 				= 3			# Radius of corner fillet on connector block
CB_SideHolePos 			= 0.6			# Proportion of connector block base length (CB_Length) to position cap attachment holes
CB_GroundWire_X 			= [CB_Width/2, CB_Length*0.75]
CB_GroundWireDiameter 		= 2 			# DIameter of ground wire channel through connector base
CB_GroundWire_Angle 		= 45			# Angle of  ground wire channel through connector base

# Chamber outer surface parameters
DefaultFullHeight 			= 40 			# Starting height of full chamber (prior to customization)
InnerChamber_filletRadius 		= 10 			# Radius of fillet used for smoothing inner chamber
OuterChamber_filletRadius 		= 5 			# Radius of fillet used for smoothing outer chamber
RidgeHeight 				= 1			# Height of each ridge on outer chamber surface
RidgeDepth 				= RidgeHeight/2 # Depth that each ridge protrudes from main surface
RidgeFillet 					= False		# Apply fillet to corners of ridges?

#=============== Create and save document
doc = FreeCAD.newDocument(filename) 	# Create new document
QtGui.QMessageBox.information(None, "NIF GenerateDualCHamber.py", "Generating default dual drive chamber...")

#=============== Generate primitives

# Create the inner Electrode A cylinder
ElecA_InnerCylinder 			= doc.addObject("Part::Cylinder", "ElecA_innerWell")
ElecA_InnerCylinder.Radius 		= Elec_RadiusA
ElecA_InnerCylinder.Height 		= DefaultFullHeight
ElecA_InnerCylinder.Placement 	= App.Placement(App.Vector(-Elec_Distance/2,0,0), App.Rotation(0,0,0))

# Create the outer Electrode A cylinder
ElecA_OuterCylinder 			= doc.addObject("Part::Cylinder", "ElecA_outerWall")
ElecA_OuterCylinder.Radius 		= Elec_RadiusA+WallThickness
ElecA_OuterCylinder.Height 		= DefaultFullHeight
ElecA_OuterCylinder.Placement 	= App.Placement(App.Vector(-Elec_Distance/2,0,0), App.Rotation(0,0,0))

# Create the outer Electrode A grid lip
ElecA_GridCylinder 			= doc.addObject("Part::Cylinder", "ElecA_gridWell")
ElecA_GridCylinder.Radius 		= Elec_RadiusA+GridLipThickness
ElecA_GridCylinder.Height 		= GridDepth
ElecA_GridCylinder.Placement 	= App.Placement(App.Vector(-Elec_Distance/2,0, DefaultFullHeight-GridDepth), App.Rotation(0,0,0))

# Create the inner Electrode B
ElecB_InnerCylinder 			= doc.addObject("Part::Cylinder", "ElecB_innerWell")
ElecB_InnerCylinder.Radius 		= Elec_RadiusB
ElecB_InnerCylinder.Height 		= DefaultFullHeight
ElecB_InnerCylinder.Placement 	= App.Placement(App.Vector(Elec_Distance/2,0,0), App.Rotation(0,0,0))

# Create the outer Electrode B cylinder
ElecB_OuterCylinder 			= doc.addObject("Part::Cylinder", "ElecB_outerWall")
ElecB_OuterCylinder.Radius 		= Elec_RadiusB+WallThickness
ElecB_OuterCylinder.Height 		= DefaultFullHeight
ElecB_OuterCylinder.Placement 	= App.Placement(App.Vector(Elec_Distance/2,0,0), App.Rotation(0,0,0))

# Create the outer Electrode B grid lip
ElecB_GridCylinder 			= doc.addObject("Part::Cylinder", "ElecB_gridWell")
ElecB_GridCylinder.Radius 		= Elec_RadiusB+GridLipThickness
ElecB_GridCylinder.Height 		= GridDepth
ElecB_GridCylinder.Placement 	= App.Placement(App.Vector(Elec_Distance/2,0, DefaultFullHeight-GridDepth), App.Rotation(0,0,0))

# Create screw holes
ScrewHole_DriveMount 		= doc.addObject("Part::Cylinder", "ScrewHole_DriveMount")
ScrewHole_DriveMount.Radius 	= 1.5
ScrewHole_DriveMount.Height 	= 5
ScrewHole_DriveMount.Placement = App.Placement(App.Vector(0,0,0), App.Rotation(90,0,0))

# Create cap screw hole
CapScrewCylinder 				= doc.addObject("Part::Cylinder", "ScrewHole_Cap")
CapScrewCylinder.Radius 			= (CapScrewDiam/2)+0.25
CapScrewCylinder.Height 			= CapScrewCutDepth
ChamferEdges(CapScrewCylinder, "CapScrewHole", [1,2,3], CapScrewChamferRadius)
doc.recompute() 	

# Duplicate cap screw holes and position
CapScrews 			= []
CapScrewOffset 		= WallThickness-CapScrewHoleDepth
CapScrewHoles_XY 		= [[-Elec_Distance/2, -Elec_RadiusA-CapScrewOffset ], [(-Elec_Distance/2)-(Elec_RadiusA+CapScrewCutDepth)-CapScrewOffset , 0], [-Elec_Distance/2, Elec_RadiusA+CapScrewCutDepth+CapScrewOffset], [Elec_Distance/2, Elec_RadiusB+CapScrewCutDepth+CapScrewOffset ], [(Elec_Distance/2)+Elec_RadiusB+CapScrewOffset, 0], [Elec_Distance/2, -Elec_RadiusB-CapScrewOffset ]]
CapScrewHoles_RotXYZ 	= [[0,0,90], [0,90,0], [0,0,90], [0,0,90], [0,90,0], [0,0,90]]
for c in range(len(CapScrewHoles_XY)):
	NewHole 		= App.ActiveDocument.copyObject(doc.CapScrewHole, True)
	NewHole.Placement 	= App.Placement(App.Vector(CapScrewHoles_XY[c][0], CapScrewHoles_XY[c][1], DefaultFullHeight - CapScrewHeight), App.Rotation(CapScrewHoles_RotXYZ[c][0],CapScrewHoles_RotXYZ[c][1],CapScrewHoles_RotXYZ[c][2]))
	CapScrews.append(NewHole.Name)

# Fuse screw holes to single object
bp 					= BOPFeatures.BOPFeatures(App.activeDocument())
CapScrews_fused 		= bp.make_multi_fuse(CapScrews)
doc.ActiveObject.Label 	= "CapScrews_fused"
CapScrewsObject		= doc.ActiveObject.Name

# Add joining blocks
if (Elec_Distance >= Elec_RadiusA+Elec_RadiusB):
	msg = "Inter-electrode distance exceeds combined radii - adding central joining block..."
	QtGui.QMessageBox.information(None, "NIF GenerateDualChamber.py", msg)
	JoinBlock_inner 				= doc.addObject("Part::Box", "JoinBlock_inner")	
	JoinBlock_inner.Length 		= Elec_Distance
	JoinBlock_inner.Width 			= min([Elec_RadiusA, Elec_RadiusB])*2
	JoinBlock_inner.Height 		= DefaultFullHeight
	JoinBlock_inner.Placement 		= App.Placement(App.Vector(-Elec_Distance/2,-JoinBlock_inner.Width/2,0), App.Rotation(0,0,0))
	
	JoinBlock_outer 				= doc.addObject("Part::Box", "JoinBlock_outer")
	JoinBlock_outer.Length 		= Elec_Distance
	JoinBlock_outer.Width 		= (min([Elec_RadiusA, Elec_RadiusB])+WallThickness)*2
	JoinBlock_outer.Height 		= DefaultFullHeight
	JoinBlock_outer.Placement 		= App.Placement(App.Vector(-Elec_Distance/2,-JoinBlock_outer.Width/2,0), App.Rotation(0,0,0))
	
	JoinBlock_grid 				= doc.addObject("Part::Box", "JoinBlock_grid")
	JoinBlock_grid.Length 		= Elec_Distance
	JoinBlock_grid.Width 			= (min([Elec_RadiusA, Elec_RadiusB])+GridLipThickness)*2
	JoinBlock_grid.Height 			= GridDepth
	JoinBlock_grid.Placement 		= App.Placement(App.Vector(-Elec_Distance/2,-JoinBlock_grid.Width/2, DefaultFullHeight-GridDepth), App.Rotation(0,0,0))	

# Create the connector block base
ConnectorBlock 				= doc.addObject("Part::Box", "ConnectorBlock")
ConnectorBlock.Length 		= CB_Length
ConnectorBlock.Width 		= CB_Width
ConnectorBlock.Height 		= CB_Height

# Fillet corners of connector block
FilletEdges(ConnectorBlock, "ConnectorBlock_Fillet", [1,3,5,7],CB_filletRadius)
#FreeCADGui.ActiveDocument.ConnectorBlock.Visibility 	= False

# Create ground wire hole and subtract from connector block base
CB_GWCylinder 				= doc.addObject("Part::Cylinder", "CB_GWcylinder")
CB_GWCylinder.Radius 		= CB_GroundWireDiameter/2
CB_GWCylinder.Height 		= CB_Height*3
#CB_GWCylinder.Placement 		= App.Placement(App.Vector(CB_GroundWire_X, 0,0), App.Rotation(0,CB_GroundWire_Angle ,0))

#bp.make_cut([ConnectorBlock_Fillet, CB_GWCylinder, ])


# Add cap screw holes to conenctor block
CB_ScrewHoleObj 			= []
ConnectorScrewHoles_XY 		= [[CB_Length*CB_SideHolePos, (CB_Width/2)-CapScrewHoleDepth+CapScrewCutDepth], [CB_Length*CB_SideHolePos,( -CB_Width/2)+CapScrewHoleDepth], [CB_Length-CapScrewHoleDepth, 0]]
ConnectorScrewHoles_RotXYZ 	= [[0,0,90], [0,0,90], [0,90,0]]
for c in range(len(ConnectorScrewHoles_XY)):
	NewHole 			= App.ActiveDocument.copyObject(doc.CapScrewHole, True)
	NewHole.Placement 	= App.Placement(App.Vector(ConnectorScrewHoles_XY[c][0], ConnectorScrewHoles_XY[c][1], DefaultFullHeight - CapScrewHeight), App.Rotation(ConnectorScrewHoles_RotXYZ[c][0], ConnectorScrewHoles_RotXYZ[c][1], ConnectorScrewHoles_RotXYZ[c][2]))
	CB_ScrewHoleObj.append(NewHole.Name)

# Center connector block, fuse and subtract screw holes
ConnectorBlock			= Draft.move(ConnectorBlock, App.Vector(0, -CB_Width/2, DefaultFullHeight-CB_Height), copy=False)
CB_ScrewHolesfused 		= bp.make_multi_fuse(CB_ScrewHoleObj)
doc.ActiveObject.Label 	= "CB_ScrewHoles"
CB_ScrewHoles			= doc.ActiveObject.Name
bp.make_cut(["ConnectorBlock_Fillet", CB_ScrewHoles,  ])
doc.ActiveObject.Label 	= "CB_withHoles"
CB_withHoles			= doc.ActiveObject.Name
doc.recompute() 	

# Move connector block to requested angle & location
doc.ActiveObject.Placement 		= App.Placement(App.Vector(0,0,0), App.Rotation(CB_Rotation_XYZ[0],CB_Rotation_XYZ[1],CB_Rotation_XYZ[2]))
##ConnectorBlock.Placement 		= App.Placement(App.Vector(0,-CB_Width/2,DefaultFullHeight-CB_Height), App.Rotation(CB_Rotation_X,0,0))

if (Elec_Distance < Elec_RadiusA+Elec_RadiusB):
	# Fuse primitive cylinder objects together
	InnerWell_fused 		= bp.make_multi_fuse(["ElecA_innerWell", "ElecB_innerWell", ])
	GridWell_fused 		= bp.make_multi_fuse(["ElecA_gridWell", "ElecB_gridWell", ])
	OuterChamber_fused 	= bp.make_multi_fuse(["ElecA_outerWall", "ElecB_outerWall", ])
	FilletEdgeIndx = [9,10]

elif (Elec_Distance >= Elec_RadiusA+Elec_RadiusB):
	# Fuse primitive cylinder objects together
	InnerWell_fused 		= bp.make_multi_fuse(["ElecA_innerWell", "ElecB_innerWell", "JoinBlock_inner", ])
	GridWell_fused 		= bp.make_multi_fuse(["ElecA_gridWell", "ElecB_gridWell", "JoinBlock_grid", ])
	OuterChamber_fused 	= bp.make_multi_fuse(["ElecA_outerWall", "ElecB_outerWall", "JoinBlock_outer", ])
	FilletEdgeIndx = [8,14]
   
# Create smooth fillet joint between intersecting pairs of cylinders
#if Elec_RadiusA != Elec_RadiusB:
FilletEdges(InnerWell_fused, "Inner_Fillet", FilletEdgeIndx,InnerChamber_filletRadius)
FilletEdges(GridWell_fused, "Grid_Fillet", FilletEdgeIndx,InnerChamber_filletRadius)
FilletEdges(OuterChamber_fused, "Outer_Fillet", FilletEdgeIndx,OuterChamber_filletRadius)

#elif Elec_RadiusA == Elec_RadiusB:
#	Inner_Fillet 	= InnerWell_fused
#	Grid_Fillet 		= GridWell_fused
#	Outer_Fillet 	= OuterChamber_fused
#	InnerWell_fused.La
#	Inner_Fillet 	= doc.getObject("InnerWell_fused")
#	Grid_Fillet 		=  doc.getObject("GridWell_fused ")
#	Outer_Fillet 	=  doc.getObject("OuterChamber_fused")

	#Inner_Fillet = App.ActiveDocument.getObjectsByLabel("Concrete wall")[0]

# Hide primitive objects
FreeCADGui.ActiveDocument.ScrewHole_Cap.Visibility 	= False
FreeCADGui.ActiveDocument.CapScrewHole.Visibility 	= False
FreeCADGui.ActiveDocument.Fusion.Visibility 		= False
FreeCADGui.ActiveDocument.Fusion001.Visibility 		= False
FreeCADGui.ActiveDocument.Fusion002.Visibility 		= False

# Fuse connector block to outer chamber
OuterChamber_fused 		= bp.make_multi_fuse(["Outer_Fillet", CB_withHoles, ])
doc.ActiveObject.Label 	= "OuterChamberSurf"
OuterChamberSurf 		= doc.ActiveObject.Name

# Subtract cap screw holes from chamber surface
bp.make_cut([OuterChamberSurf, CapScrewsObject,  ])
doc.ActiveObject.Label 	=  "OuterChamber_wHoles"
OuterChamberSurface	= doc.ActiveObject.Name
doc.recompute() 	

# Duplciate outer surface and convert to chamfered 'ridge'
doc.recompute() 												# Display results in GUI
App.ActiveDocument.copyObject(App.ActiveDocument.Outer_Fillet, True)
doc.getObject('ElecA_outerWall001').Height 	= 1
doc.getObject('ElecB_outerWall001').Height 	= 1
doc.getObject('ElecA_outerWall001').Radius 	= Elec_RadiusA + WallThickness +RidgeDepth
doc.getObject('ElecB_outerWall001').Radius 	= Elec_RadiusB + WallThickness +RidgeDepth
Ridge 		= doc.getObject('Outer_Fillet001')
NoEdges 		= int(len(Ridge.Shape.Edges))
RidgeEdgeIndx 	= list(range(1,  NoEdges+1))
ChamferEdges(Ridge, "Ridge",  RidgeEdgeIndx, (RidgeHeight /2)-0.05)

# Stack ridges along height of chamber
doc.recompute() 												# Display results in GUI
NoRidges 		= int((DefaultFullHeight-CapLipDepth)/RidgeHeight)
RidgeHeights 	= np.linspace(RidgeHeight, DefaultFullHeight-CapLipDepth, NoRidges-1)
AllRidges 		= ["Ridge"]
for r in range(NoRidges-1):
	NewRidge 			= App.ActiveDocument.copyObject(App.ActiveDocument.Ridge, True)
	NewRidge.Placement 	= App.Placement(App.Vector(0,0, RidgeHeights[r]), App.Rotation(0,0,0))
	#print(NewRidge.Name)
	AllRidges.append(NewRidge.Name)
	del NewRidge

# Merge Ridges
Ridges_fused 			= bp.make_multi_fuse(AllRidges)
doc.ActiveObject.Label 	= "Ridges"
Ridges 				= doc.ActiveObject.Name
doc.recompute() 	

# Fuse inner chamber parts
Inner_fused 			= bp.make_multi_fuse([ "Inner_Fillet", "Grid_Fillet",  ])
doc.ActiveObject.Label 	= "InnerChamber"
InnerChamber 			= doc.ActiveObject.Name
doc.recompute() 	

# Fuse outer chamber parts
Outer_fused 			= bp.make_multi_fuse([Ridges, OuterChamberSurface,  ])
doc.ActiveObject.Label 	= "OuterChamber"
OuterChamber 			= doc.ActiveObject.Name
doc.recompute() 	

# Subtract inner chamber well from outer chamber walls
bp.make_cut([OuterChamber, InnerChamber,  ])
doc.ActiveObject.Label 	= "ChamberSurface"

# Finish up
App.ActiveDocument.recompute()
doc.recompute() 						# Display results in GUI
Gui.SendMsgToActiveView("ViewFit")			# Set GUI window view to fit
Gui.activeDocument().activeView().viewTop() 		# Set GUI window view from top
#doc.saveAs([filename,'.FCStd'])						# Save file?

# Export .STL file
