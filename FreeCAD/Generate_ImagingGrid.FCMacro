#================== Generate_ImagingGrid.py ===================
# This script generates a CAD model of a grid that can be attached to a temporary 
# chamber cap for imaging the position of the implanted chamber relatvie to 
# neural targets. The grid holes will need to be filled with contrast agent appropriate 
# to the imaging modality.  For more information, see: https://py-ignite.readthedocs.io/en/latest/ImplantDesign.html
#     _________  ________     ____    ___  _________  _________  _______
#    /__   ___/ /  _____/    /    |  /  / /__   ___/ /__   ___/ /  ____/
#      /  /    /  / ___     /     | /  /    /  /       /  /    /  /___
#     /  /    |  | |_  |   /  /|  |/  /    /  /       /  /    /  ____/
#  __/  /__   |  \__/  /  /  / |     /  __/  /__     /  /    /  /____
# /_______/    \______/  /__/  |____/  /_______/    /__/    /_______/
#
# Image-Guided Neural Implantation Targeting Extensions
# https://py-ignite.rtfd.io
#=========================================================

import FreeCAD as App
import Part
import Draft
import numpy as np
from BOPTools import BOPFeatures

#======== Apply fillet to object edges
def FilletEdges(Object, FilletName, FilletEdges, FilletRadius):
	Fillet 		= doc.addObject("Part::Fillet", FilletName)
	Fillet.Base 	= Object
	__fillets__ = []
	if isinstance(FilletEdges, str ) and FilletEdges.casefold() == 'all':
		NoEdges 	= len(Object.Shape.Edges)
		FilletEdges = np.linspace(1, NoEdges, NoEdges).tolist()
	for n in FilletEdges:
	  __fillets__.append((n, FilletRadius, FilletRadius))
	Fillet.Edges 		= __fillets__
	Object.Visibility 	= False
	del __fillets__
	return Fillet



#=============== Set parameters
filename 				= "TEST"
Outer_Diameter 			= 25 						# Outer diameter of main grid cylinder
GridHole_Diameter 		= 2 						# Diameter of each grid hole (mm)
GridHole_Depth 			= 30						# Length of grid holes
AlignmentDepth 			= 4 						# 
Base_Depth 			= 5						# Depth of the grid base
Base_Diameter 			= 34 						# Diameter of the grid base (attahcment point to cap)
GridHole_NoPerRing 		= [8,8]					# Number o fgrid holes for each concentric ring around the center hole
GridHole_ArrayRadii   		= [5,8]*GridHole_Diameter	# Radius from center for each concentric ring of grid holes
GridHole_angles 			= [0,0,0]					# Angles to rotate the grid holes in degrees about the X,Y and Z axes
ScrewHole_Diameter 		= 3 						# Diameter of through-hole for attachment screws
ScrewHole_HeadRadius 	= ScrewHole_Diameter*0.75 	# Daimater of screw head countersink holes

# Check parameters are consistent
if (GridHole_ArrayRadii[-1] + GridHole_Diameter) > Outer_Diameter:
	print('Warning: selected grid hole array radius exceeds the requested outer diameter!')


#=============== Create and save document
FullFilename = "ImagingGrid_%s" % (filename)
doc 	= FreeCAD.newDocument(FullFilename) 				# Create new document
bp 	= BOPFeatures.BOPFeatures(App.activeDocument())		

#=============== Generate primitives
print("Creating chamber primitives...\n")

# Create the main outer cylinder
OuterCylinder 				= doc.addObject("Part::Cylinder", "OuterCylinder")
OuterCylinder.Radius 			= Outer_Diameter/2
OuterCylinder.Height 			= GridHole_Depth+AlignmentDepth+2
OuterCylinder.Placement 		= App.Placement(App.Vector(0,0,0), App.Rotation(GridHole_angles[0],GridHole_angles[1],GridHole_angles[2]))
OuterCylinder 				= FilletEdges(OuterCylinder, "OuterCylinder", "all", 2)

# Create base cylinder
BaseCylinder 				= doc.addObject("Part::Cylinder", "BaseCylinder")
BaseCylinder.Radius 			= Base_Diameter/2
BaseCylinder.Height 			= Base_Depth
BaseCylinder.Placement 		= App.Placement(App.Vector(0,0,0), App.Rotation(0,0,0))

OuterGrid					= bp.make_multi_fuse([OuterCylinder.Name, BaseCylinder.Name, ])
OuterGrid.ViewObject.Transparency = 50

# Create the origin grid hole cylinder
GridCylinder 				= doc.addObject("Part::Cylinder", "GridCylinder")
GridCylinder.Radius 			= GridHole_Diameter/2
GridCylinder.Height 			= GridHole_Depth
GridCylinder.Placement 		= App.Placement(App.Vector(0,0,0), App.Rotation(GridHole_angles[0],GridHole_angles[1],GridHole_angles[2]))

# Create additional grid holes
GridHoles 					= [GridCylinder.Name]
for c in range(0, len(GridHole_NoPerRing)):
	GridHole_RadialAngles 		= np.deg2rad(np.linspace(0,360, GridHole_NoPerRing[c]+1))
	for n in range(0, GridHole_NoPerRing[c]):
		NewHole 	= Draft.clone(GridCylinder)
		Pos 		= [np.sin(GridHole_RadialAngles[n])*GridHole_ArrayRadii[c], np.cos(GridHole_RadialAngles[n])*GridHole_ArrayRadii[c]]
		NewHole.Placement = App.Placement(App.Vector(Pos[0],Pos[1],0),  App.Rotation(GridHole_angles[0],GridHole_angles[1],GridHole_angles[2]))
		GridHoles.append(NewHole.Name)

AllGridHoles 	= bp.make_multi_fuse(GridHoles)

# Create base alignment blocks
Block_A					= doc.addObject("Part::Box", "Block_A")	
Block_A.Length 				= Base_Diameter*2
Block_A.Width 				= AlignmentDepth*2
Block_A.Height 				= AlignmentDepth*2
VertOffset 				= np.sin(np.deg2rad(45))*AlignmentDepth*2
Block_A.Placement 			= App.Placement(App.Vector(-Base_Diameter*0.75, 0, AlignmentDepth-VertOffset*2), App.Rotation(0,0,45))
Block_B 					= Draft.clone(Block_A)
Block_B.Placement 			= App.Placement(App.Vector(0, -Base_Diameter*0.75, AlignmentDepth-VertOffset*2), App.Rotation(90,0,45))
AlignBlock_Lower 			= bp.make_multi_fuse([Block_A.Name, Block_B.Name, ])
AlignBlock_Upper 			= Draft.clone(AlignBlock_Lower)
AlignBlock_Upper.Placement 	= App.Placement(App.Vector(0, 0 , GridHole_Depth+AlignmentDepth+3+VertOffset), App.Rotation(0,0,0))
OuterGrid 					= bp.make_cut([OuterGrid.Name, AlignBlock_Lower.Name, ])
OuterGrid 					= bp.make_cut([OuterGrid.Name, AlignBlock_Upper.Name, ])

# Import screw STEP files
IgniteDir 		= '/Volumes/NIFVAULT/projects/murphyap_NIF/NIF_Code/IGNITE/FreeCAD/'
ScrewFile 		= os.path.join(IgniteDir, 'Parts/Screws/96295A120_Narrow Cheese Head Slotted Screws.STEP')
Screw 		= App.ActiveDocument.addObject("Part::Feature","M3_screw")
Screw.Shape 	= Part.read(ScrewFile)

# Create cap attachment screw holes
ScrewHole 				= doc.addObject("Part::Cylinder", "ScrewHole")
ScrewHole.Radius 			= ScrewHole_Diameter/2
ScrewHole.Height 			= Base_Depth +2
ScrewHole.Placement 			= App.Placement(App.Vector(0,0,-1), App.Rotation(0,0,0))
ScrewHoles 				= []
ScrewHole_XY 				= [[-1,1], [1,1],[1,-1],[-1,-1]]
ScrewHole_Offset 			= ((Base_Diameter/2)*np.sin(np.deg2rad(45)))-ScrewHole_Diameter
ScrewHead 				= doc.addObject("Part::Cylinder", "ScrewHead")
ScrewHead.Radius 			= ScrewHole_HeadRadius
ScrewHead.Height 			= GridHole_Depth
ScrewHead.Placement 		= App.Placement(App.Vector(0,0,Base_Depth), App.Rotation(0,0,0))
ScrewHole 				= bp.make_multi_fuse([ScrewHole.Name, ScrewHead.Name, ])

for s in range(0, len(ScrewHole_XY)):
	NewHole 			= Draft.clone(ScrewHole)
	NewHole.Placement 	= App.Placement(App.Vector(ScrewHole_XY[s][0]*ScrewHole_Offset, ScrewHole_XY[s][1]*ScrewHole_Offset,0), App.Rotation(0,0,0))
	ScrewHoles.append(NewHole.Name)
	NewScrew 			= Draft.clone(Screw)
	NewScrew.Placement 	= App.Placement(App.Vector(ScrewHole_XY[s][0]*ScrewHole_Offset, ScrewHole_XY[s][1]*ScrewHole_Offset,Base_Depth), App.Rotation(0,0,0))

ScrewHole.Visibility 	= False
Screw.Visibility 		= False
AllScrewHoles 		= bp.make_multi_fuse(ScrewHoles)
OuterGrid 			= bp.make_cut([OuterGrid.Name, AllScrewHoles.Name, ])


#============ Finish up
FreeCADGui.updateGui()
doc.recompute() 						# Display results in GUI
Gui.SendMsgToActiveView("ViewFit")			# Set GUI window view to fit
